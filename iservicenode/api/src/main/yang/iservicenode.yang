module iservicenode {
    yang-version 1;
    namespace "urn:opendaylight:params:xml:ns:yang:iservicenode";
    prefix "iservicenode";

    revision "2015-01-05" {
        description "Initial revision of iservicenode model";
    }

    container getTopology {
        uses nodes;
        uses links;
    }
    
    rpc add-node {
        input {
            leaf nodeIpAddress {
                type string;
            }
        }
        output {
            leaf response {
                type string;
            }
        }
    }

    grouping nodes {
        list node {
            leaf deviceType {
                type string;
                config false;
            }
            leaf label {
                type string;
                config false;
            }
            leaf ip {
                type ip-address;
                config false;
            }
            leaf softwareVersion {
                type string;
                config false;
            }
            leaf nodeType {
                type string;
                config false;
            }
            leaf family {
                type string;
                config false;
            }
            leaf platformId {
                type string;
                config false;
            }
            list tags {
                leaf tag {
                    type string;
                    config false;
                }
            }
            leaf role {
                type string;
                config false;
            }
            leaf roleSource {
                type string;
                config false;
            }
            container customParam {
                uses object;
                config false;
            }
            leaf id {
                type string;
                config false;
            }
        }
    }

    grouping links {
        list link {
            leaf source {
                type string;
                config false;
            }
            leaf startPortID {
                type string;
                config false;
            }
            leaf startPortName {
                type string;
                config false;
            }
            leaf startPortIpv4Address {
                type ip-address;
                config false;
            }
            leaf startPortIpv4Mask {
                type ip-address;
                config false;
            }
            leaf startPortSpeed {
                type uint32;
                config false;
            }
            leaf target {
                type string;
                config false;
            }
            leaf endPortID {
                type string;
                config false;
            }
            leaf endPortName {
                type string;
                config false;
            }
            leaf endPortIpv4Address {
                type ip-address;
                config false;
            }
            leaf endPortIpv4Mask {
                type ip-address;
                config false;
            }
            leaf endPortSpeed {
                type uint32;
                config false;
            }
            leaf linkStatus {
                type string;
                config false;
            }
            leaf id {
                type uint16;
                config false;
            }
            
        }
    }
    
    grouping object {
        leaf property1 {
            type string;
            config false;
        }
        leaf property2 {
            type string;
            config false;
        }
    }
    
    typedef ip-address {
      type union {
        type ipv4-address;
        type ipv6-address;
      }
      description
        "The ip-address type represents an IP address and is IP
      version neutral.  The format of the textual representation
      implies the IP version.  This type supports scoped addresses
      by allowing zone identifiers in the address format.";
      reference
        "RFC 4007: IPv6 Scoped Address Architecture";

    }

    typedef ipv4-address {
      type string {
        pattern
          '(([0-9]|[1-9][0-9]|1[0-9][0-9]|2[0-4][0-9]|25[0-5])\.){3}([0-9]|[1-9][0-9]|1[0-9][0-9]|2[0-4][0-9]|25[0-5])(%[\p{N}\p{L}]+)?';
      }
      description
        "The ipv4-address type represents an IPv4 address in
       dotted-quad notation.  The IPv4 address may include a zone
       index, separated by a % sign.

       The zone index is used to disambiguate identical address
       values.  For link-local addresses, the zone index will
       typically be the interface index number or the name of an
       interface.  If the zone index is not present, the default
       zone of the device will be used.

       The canonical format for the zone index is the numerical
       format";
    }

    typedef ipv6-address {
      type string {
        pattern
          '((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))(%[\p{N}\p{L}]+)?';
        pattern
          '(([^:]+:){6}(([^:]+:[^:]+)|(.*\..*)))|((([^:]+:)*[^:]+)?::(([^:]+:)*[^:]+)?)(%.+)?';
      }
      description
        "The ipv6-address type represents an IPv6 address in full,
      mixed, shortened, and shortened-mixed notation.  The IPv6
      address may include a zone index, separated by a % sign.

      The zone index is used to disambiguate identical address
      values.  For link-local addresses, the zone index will
      typically be the interface index number or the name of an
      interface.  If the zone index is not present, the default
      zone of the device will be used.



      The canonical format of IPv6 addresses uses the textual
      representation defined in Section 4 of RFC 5952.  The
      canonical format for the zone index is the numerical
      format as described in Section 11.2 of RFC 4007.";
      reference
        "RFC 4291: IP Version 6 Addressing Architecture
         RFC 4007: IPv6 Scoped Address Architecture
         RFC 5952: A Recommendation for IPv6 Address Text
              Representation";

    }
}
